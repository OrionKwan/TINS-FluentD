-- =================================================================
-- 
-- Description	: This MIB defines the managed objects that are used
--                 by the function interfaces of the SNMP Northbound 
--                 Interface. The definitions decide what operations
--                 the NMS can do and what network management 
--                 information the NMS can obtain.
-- Reference	: 
-- Version		: V1.00
-- History		:
-- <Huawei Technologies Ltd.>,<10 August 2007>,<Created>
-- =================================================================
--  

	IMAP_NORTHBOUND_MIB-V1 DEFINITIONS ::= BEGIN
 
		IMPORTS
			OBJECT-TYPE			
				FROM RFC-1212			
			TRAP-TYPE			
				FROM RFC-1215			
			enterprises			
				FROM RFC1155-SMI;
	
	
--
-- Node definitions
--
	
-- This MIB defines the managed objects that are used
-- by the function interfaces of the SNMP Northbound 
-- Interface.
		iMAP OBJECT IDENTIFIER ::= { enterprises 2011 }

		
		products OBJECT IDENTIFIER ::= { iMAP 2 }

		
		iMAPNetManagement OBJECT IDENTIFIER ::= { products 15 }

		
		iMAPNorthbound OBJECT IDENTIFIER ::= { iMAPNetManagement 2 }

		
		iMAPNorthboundCommon OBJECT IDENTIFIER ::= { iMAPNorthbound 1 }

		
		iMAPNorthboundEventMgmt OBJECT IDENTIFIER ::= { iMAPNorthboundCommon 2 }

		
		iMAPNorthboundNotificationReport OBJECT IDENTIFIER ::= { iMAPNorthboundEventMgmt 1 }

		
		iMAPNorthboundNotificationCommon OBJECT IDENTIFIER ::= { iMAPNorthboundNotificationReport 1 }

		
		iMAPNorthboundHeartbeatNotification OBJECT IDENTIFIER ::= { iMAPNorthboundNotificationCommon 1 }

		
--   Description: This is the Heartbeat Notification Trap Group
-- It contains the Heartbeat Notification Trap
-- OID        : 1.3.6.1.4.1.2011.2.15.2.1.2.1.1.1.0
-- 
		iMAPNorthboundHeartbeatNotificationV2 OBJECT IDENTIFIER ::= { iMAPNorthboundHeartbeatNotification 0 }

		
--   Name       : iMAPNorthboundHeartbeatSystemLabel 
-- Description: This is the iMAP system ID
-- OID        : 1.3.6.1.4.1.2011.2.15.2.1.2.1.1.1.1
-- Type       : Octet string
-- 
		iMAPNorthboundHeartbeatSystemLabel OBJECT-TYPE
			SYNTAX OCTET STRING
			ACCESS read-only
			STATUS mandatory
			DESCRIPTION
				"Managed system ID: indicates the managed system from which the heartbeat notification is reported.
				It uniquely identifies one EMS."
			::= { iMAPNorthboundHeartbeatNotification 1 }

		
--   Name:        iMAPNorthboundHeartbeatPeriod
-- Description: Heartbeat period (must be between 3 and 3600), in seconds
-- OID :        1.3.6.1.4.1.2011.2.15.2.1.2.1.1.1.2
-- Type:        Integer32
-- 
		iMAPNorthboundHeartbeatPeriod OBJECT-TYPE
			SYNTAX INTEGER
			ACCESS read-only
			STATUS mandatory
			DESCRIPTION
				"Heartbeat period (must be between 3 and 3600), in seconds"
			::= { iMAPNorthboundHeartbeatNotification 2 }

		
--   Name       : iMAPNorthboundHeartbeatTimeStamp
-- Description: Timestamp, the time when the heartbeat
--              notification trap is generated
-- OID        : 1.3.6.1.4.1.2011.2.15.2.1.2.1.1.1.3	
-- Type       : Octet string
-- 
		iMAPNorthboundHeartbeatTimeStamp OBJECT-TYPE
			SYNTAX OCTET STRING
			ACCESS read-only
			STATUS mandatory
			DESCRIPTION
				"Time stamp: the time when the heartbeat notification trap is generated"
			::= { iMAPNorthboundHeartbeatNotification 3 }

		
		iMAPNorthboundCommuLinkMonitor OBJECT IDENTIFIER ::= { iMAPNorthboundCommon 3 }

		
		iMAPNorthboundHeartbeatSvc OBJECT IDENTIFIER ::= { iMAPNorthboundCommuLinkMonitor 1 }

		
--   iMAPNorthboundHeartbeatSvcReportInterval - Used to set
-- the heartbeat interval. The range is 3 - 3600 seconds. 
-- 
-- OID = 1.3.6.1.4.1.2011.2.15.2.1.3.1.1
-- 
		iMAPNorthboundHeartbeatSvcReportInterval OBJECT-TYPE
			SYNTAX INTEGER (3..3600)
			ACCESS read-write
			STATUS mandatory
			DESCRIPTION
				"Accepts integral values in the range 3-3600 (both end inclusive), in seconds.
				Sets heartbeat interval to the value supplied (in seconds). A heart beat
				is sent immediately consisting of changed interval.
				Attempt to set with invalid value results in error.
				
				Get attempt on this node will return the current heartbeat interval.
				This parameter can be set if heartbeat configuration is enabled in snmpsvc.xml"
			::= { iMAPNorthboundHeartbeatSvc 1 }

		
		iMAPNorthboundFault OBJECT IDENTIFIER ::= { iMAPNorthbound 4 }

		
		iMAPNorthboundFaultQuery OBJECT IDENTIFIER ::= { iMAPNorthboundFault 1 }

		
--   iMAPNorthboundAlarmQuery - Leaf node that triggers active/current alarms query.
-- If the interface value is set to 1, the iMAP starts querying 
-- active/current alarms and reports them as traps to the NMS. If the value
-- is set to 0, the iMAP stops querying the active/current alarms and will
-- not report them to the NMS.
-- 
-- OID = 1.3.6.1.4.1.2011.2.15.2.4.1.5
-- 
		iMAPNorthboundAlarmQuery OBJECT-TYPE
			SYNTAX OCTET STRING
			ACCESS read-write
			STATUS mandatory
			DESCRIPTION
				"Accepts only values 0 and 1 (single character)
				Attempt to set any other value returns error
				1-> starts query active/current alarm process (if previous query alarm process is in progress then error is returned)
				0-> stops the previous query active/current alarm process in progress (if any)
				
				Get attempt on this node will return the previously set value."
			::= { iMAPNorthboundFaultQuery 5 }

		
		iMAPNorthboundFaultNotification OBJECT IDENTIFIER ::= { iMAPNorthboundFault 3 }

		
		iMAPNorthboundFaultAlarmNotification OBJECT IDENTIFIER ::= { iMAPNorthboundFaultNotification 3 }

		
--   Description: This is Fault Alarm Notification Group
-- It contains the Fault Alarm Traps for 
-- sending real-time alarms to NMS
-- OID        : 1.3.6.1.4.1.1.2.15.2.4.3.3.0
-- 
		iMAPNorthboundFaultAlarmNotificationV2 OBJECT IDENTIFIER ::= { iMAPNorthboundFaultAlarmNotification 0 }

		
--   Name       : iMAPNorthboundAlarmCSN
-- Description: Serial number of an alarm. An alarm is identified
--              by a unique number. 	
-- OID        : 1.3.6.1.4.1.2011.2.15.2.4.3.3.1	
-- Type       : Octet string
-- 
		iMAPNorthboundAlarmCSN OBJECT-TYPE
			SYNTAX OCTET STRING
			ACCESS read-only
			STATUS mandatory
			DESCRIPTION
				"Serial number of an alarm > 0.
				An alarm is identified by a unique number."
			::= { iMAPNorthboundFaultAlarmNotification 1 }

		
--   Name       : iMAPNorthboundAlarmCategory
-- Description: Alarm category.
--              1 - Fault
--              2 - Clear
--              3 - Event
--              4 - Acknowledge
--              5 - Unacknowledge
--              9 - Change	
-- OID        : 1.3.6.1.4.1.2011.2.15.2.4.3.3.2	
-- Type       : Octet string
-- 
		iMAPNorthboundAlarmCategory OBJECT-TYPE
			SYNTAX OCTET STRING
			ACCESS read-only
			STATUS mandatory
			DESCRIPTION
				"Category can be one of the following:
				1 - Fault
				2 - Clear
				3 - Event
				4 - Acknowledge
				5 - Unacknowledge
				9 - Change
				"
			::= { iMAPNorthboundFaultAlarmNotification 2 }

		
--   Name        : iMAPNorthboundAlarmOccurTime
-- Description : Fault occurrence time, time at which the alarm has been raised	
-- OID         : 1.3.6.1.4.1.2011.2.15.2.4.3.3.3	
-- Type        : Octet string
-- 
		iMAPNorthboundAlarmOccurTime OBJECT-TYPE
			SYNTAX OCTET STRING
			ACCESS read-only
			STATUS mandatory
			DESCRIPTION
				"Fault occurrence time, time at which the alarm has been raised.
				This node's value is dependent on UTCTime and timetype parameters in snmpsvc.xml"
			::= { iMAPNorthboundFaultAlarmNotification 3 }

		
--   Name        : iMAPNorthboundAlarmMOName
-- Description : Managed object name for which the alarm has been raised.	
-- OID         : 1.3.6.1.4.1.2011.2.15.2.4.3.3.4	
-- Type        : Octet string
-- 
		iMAPNorthboundAlarmMOName OBJECT-TYPE
			SYNTAX OCTET STRING
			ACCESS read-only
			STATUS mandatory
			DESCRIPTION
				"Managed object name for which the alarm has been raised"
			::= { iMAPNorthboundFaultAlarmNotification 4 }

		
--   Name        : iMAPNorthboundAlarmProductID
-- Description : Product ID.	
-- OID         : 1.3.6.1.4.1.2011.2.15.2.4.3.3.5	
-- Type        : Integer
-- 
		iMAPNorthboundAlarmProductID OBJECT-TYPE
			SYNTAX INTEGER
				{
				transmission(1),
				mobile(2),
				fixedNetworkNarrow(3),
				bandFixedBand(4),
				intelligence(5),
				omc(6)
				}
			ACCESS read-only
			STATUS mandatory
			DESCRIPTION
				"Product type ID:
				1 - transmission
				2 - mobile
				3 - fixed network narrowband
				4 - fixed network broadband
				5 - intelligent network
				6 - omc"
			::= { iMAPNorthboundFaultAlarmNotification 5 }

		
--   Name        : iMAPNorthboundAlarmNEType
-- Description : Network Element Type ID. 
--               The NMS obtains the device type list from the iMAP
--               administrator by using a method other than SNMP.              
-- 	
-- OID         : 1.3.6.1.4.1.2011.2.15.2.4.3.3.6	
-- Type        : Octet String
-- 
		iMAPNorthboundAlarmNEType OBJECT-TYPE
			SYNTAX OCTET STRING
			ACCESS read-only
			STATUS mandatory
			DESCRIPTION
				"Network Element Type ID"
			::= { iMAPNorthboundFaultAlarmNotification 6 }

		
--   Name        : iMAPNorthboundAlarmNEDevID
-- Description : Network Element or Device ID       
-- OID         : 1.3.6.1.4.1.2011.2.15.2.4.3.3.7	
-- Type        : Octet String
-- 
		iMAPNorthboundAlarmNEDevID OBJECT-TYPE
			SYNTAX OCTET STRING
			ACCESS read-only
			STATUS mandatory
			DESCRIPTION
				"Network Element or Device ID"
			::= { iMAPNorthboundFaultAlarmNotification 7 }

		
--   Name        : iMAPNorthboundAlarmDevCsn
-- Description :Device Serial number of the alarm device, unique in the same NE.      
-- OID         : 1.3.6.1.4.1.2011.2.15.2.4.3.3.8	
-- Type        : Octet String
-- 
		iMAPNorthboundAlarmDevCsn OBJECT-TYPE
			SYNTAX OCTET STRING
			ACCESS read-only
			STATUS mandatory
			DESCRIPTION
				"Device Serial number of the alarm device, unique in the same NE."
			::= { iMAPNorthboundFaultAlarmNotification 8 }

		
--   Name        : iMAPNorthboundAlarmID
-- Description : Alarm ID for the raised alarm.
--               It identifies the type of alarm from the device
--               of the same type.      
-- OID         : 1.3.6.1.4.1.2011.2.15.2.4.3.3.9	
-- Type        : Integer32
-- 
		iMAPNorthboundAlarmID OBJECT-TYPE
			SYNTAX INTEGER
			ACCESS read-only
			STATUS mandatory
			DESCRIPTION
				"Alarm ID for the raised alarm"
			::= { iMAPNorthboundFaultAlarmNotification 9 }

		
--   Name        : iMAPNorthboundAlarmType
-- Description : Alarm type.
--               1 - Power System
--               2 - Environment System
--               3 - Signaling System
--               4 - Trunk System
--               5 - Hardware System
--               6 - Software System
--               7 - Running System
--               8 - Communication System
--               9 - QoS
--               10 - Processing error
--               11 - OMC
--               12 - Integrity Violation
--               13 - Operational Violation
--               14 - Physical Violation
--               15 - Security Service Or Mechanism Violation
--               16 - Time Domain Violation
--      
-- OID         : 1.3.6.1.4.1.2011.2.15.2.4.3.3.10	
-- Type        : Integer32
-- 
		iMAPNorthboundAlarmType OBJECT-TYPE
			SYNTAX INTEGER
				{
				powerSystem(1),
				environmentSystem(2),
				signalingSystem(3),
				trunkSystem(4),
				hardwareSystem(5),
				softwareSystem(6),
				runningSystem(7),
				communicationSystem(8),
				qos(9),
				processingError(10),
			    omc(11),
				integrityViolation(12),
				operationalViolation(13),
				physicalViolation(14),
				securityServiceOrMechanismViolation(15),
			    timeDomainViolation(16)								
			    }
			ACCESS read-only
			STATUS mandatory
			DESCRIPTION
				"Alarm type. It can be one of the following:
					1 - Power System
					2 - Environment System
					3 - Signaling System
					4 - Trunk System
					5 - Hardware System
					6 - Software System
					7 - Running System
					8 - Communication System
					9 - QoS
					10 - Processing error
					11 - OMC
					12 - Integrity Violation
					13 - Operational Violation
					14 - Physical Violation
					15 - Security Service Or Mechanism Violation
					16 - Time Domain Violation"
			::= { iMAPNorthboundFaultAlarmNotification 10 }

		
--   Name        : iMAPNorthboundAlarmLevel
-- Description : Alarm level.
--               1 - Critical 
--               2 - Major
--               3 - Minor
--               4 - Warning
--               5 - Indeterminate
--               6 - Clear
--      
-- OID         : 1.3.6.1.4.1.2011.2.15.2.4.3.3.11	
-- Type        : Integer
-- 
		iMAPNorthboundAlarmLevel OBJECT-TYPE
			SYNTAX INTEGER
				{
				critical(1),
				major(2),
				minor(3),
				warning(4),
				indeterminate(5),
				clear(6)
				}
			ACCESS read-only
			STATUS mandatory
			DESCRIPTION
				"Level is the alarm severity. It can be one of the following: 
				1 - Critical                 
				2 - Major                    
				3 - Minor                    
				4 - Warning                  
				5 - Indeterminate
				6 - Clear"
			::= { iMAPNorthboundFaultAlarmNotification 11 }

		
--   Name        : iMAPNorthboundAlarmRestore
-- Description : Alarm clearance ID.
--               1 - Cleared
--               2 - Uncleared.
-- 
-- OID         : 1.3.6.1.4.1.2011.2.15.2.4.3.3.12	
-- Type        : Integer
-- 
		iMAPNorthboundAlarmRestore OBJECT-TYPE
			SYNTAX INTEGER
				{
				cleared(1),
				uncleared(2)
				}
			ACCESS read-only
			STATUS mandatory
			DESCRIPTION
				"Alarm clear status 
				1 - Cleared 
				2 - Uncleared"
			::= { iMAPNorthboundFaultAlarmNotification 12 }

		
--   Name        : iMAPNorthboundAlarmConfirm
-- Description : Alarm acknowledgement ID.
--               1- Acknowledged
--               2 - Unacknowledged
-- 
-- OID         : 1.3.6.1.4.1.2011.2.15.2.4.3.3.13	
-- Type        : Integer
-- 
		iMAPNorthboundAlarmConfirm OBJECT-TYPE
			SYNTAX INTEGER
				{
				acknowledged(1),
				unacknowledged(2)
				}
			ACCESS read-only
			STATUS mandatory
			DESCRIPTION
				"Alarm acknowledgement status 
				1 - Acknowledged 
				2 - Unacknowledged "
			::= { iMAPNorthboundFaultAlarmNotification 13 }

		
--   Name        : iMAPNorthboundAlarmAckTime
-- Description : Alarm acknowledgement time
-- OID         : 1.3.6.1.4.1.2011.2.15.2.4.3.3.14	
-- Type        : Octet String
-- 
		iMAPNorthboundAlarmAckTime OBJECT-TYPE
			SYNTAX OCTET STRING
			ACCESS read-only
			STATUS mandatory
			DESCRIPTION
				"Alarm acknowledgement time.
				This node's value is dependent on UTCTime and timetype parameters in snmpsvc.xml"
			::= { iMAPNorthboundFaultAlarmNotification 14 }

		
--   Name        : iMAPNorthboundAlarmRestoreTime
-- Description : Alarm clearance time
-- OID         : 1.3.6.1.4.1.2011.2.15.2.4.3.3.15	
-- Type        : Octet String
-- 
		iMAPNorthboundAlarmRestoreTime OBJECT-TYPE
			SYNTAX OCTET STRING
			ACCESS read-only
			STATUS mandatory
			DESCRIPTION
				"Alarm clearance time.
				This node's value is dependent on UTCTime and timetype parameters in snmpsvc.xml"
			::= { iMAPNorthboundFaultAlarmNotification 15 }

		
--  Name        : iMAPNorthboundAlarmOperator
-- Description : Operator, who performs the acknowledgement and clearance operations.
-- OID         : 1.3.6.1.4.1.2011.2.15.2.4.3.3.16	
-- Type        : Octet String
		iMAPNorthboundAlarmOperator OBJECT-TYPE
			SYNTAX OCTET STRING
			ACCESS read-only
			STATUS mandatory
			DESCRIPTION
				"Operator, who performs the acknowledgement and clearance operations."
			::= { iMAPNorthboundFaultAlarmNotification 16 }

		
--   Name        : iMAPNorthboundAlarmParas1
-- Description : Reserved field 1.
-- OID         : 1.3.6.1.4.1.2011.2.15.2.4.3.3.17	
-- Type        : Integer32
-- 
		iMAPNorthboundAlarmParas1 OBJECT-TYPE
			SYNTAX INTEGER
			ACCESS read-only
			STATUS mandatory
			DESCRIPTION
				"Reserved field 1"
			::= { iMAPNorthboundFaultAlarmNotification 17 }

		
--   Name        : iMAPNorthboundAlarmParas2
-- Description : Reserved field 2.
-- OID         : 1.3.6.1.4.1.2011.2.15.2.4.3.3.18	
-- Type        : Integer32
-- 
		iMAPNorthboundAlarmParas2 OBJECT-TYPE
			SYNTAX INTEGER
			ACCESS read-only
			STATUS mandatory
			DESCRIPTION
				"Reserved field 2"
			::= { iMAPNorthboundFaultAlarmNotification 18 }

		
--   Name        : iMAPNorthboundAlarmParas3
-- Description : Reserved field 3.
-- OID         : 1.3.6.1.4.1.2011.2.15.2.4.3.3.19	
-- Type        : Integer32
-- 
		iMAPNorthboundAlarmParas3 OBJECT-TYPE
			SYNTAX INTEGER
			ACCESS read-only
			STATUS mandatory
			DESCRIPTION
				"Reserved field 3"
			::= { iMAPNorthboundFaultAlarmNotification 19 }

		
--   Name        : iMAPNorthboundAlarmParas4
-- Description : Reserved field 4.
-- OID         : 1.3.6.1.4.1.2011.2.15.2.4.3.3.20	
-- Type        : Integer32
-- 
		iMAPNorthboundAlarmParas4 OBJECT-TYPE
			SYNTAX INTEGER
			ACCESS read-only
			STATUS mandatory
			DESCRIPTION
				"Reserved field 4"
			::= { iMAPNorthboundFaultAlarmNotification 20 }

		
--   Name        : iMAPNorthboundAlarmParas5
-- Description : Reserved field 5.
-- OID         : 1.3.6.1.4.1.2011.2.15.2.4.3.3.21	
-- Type        : Integer32
-- 
		iMAPNorthboundAlarmParas5 OBJECT-TYPE
			SYNTAX INTEGER
			ACCESS read-only
			STATUS mandatory
			DESCRIPTION
				"Reserved field 5"
			::= { iMAPNorthboundFaultAlarmNotification 21 }

		
--   Name        : iMAPNorthboundAlarmParas6
-- Description : Reserved field 6.
-- OID         : 1.3.6.1.4.1.2011.2.15.2.4.3.3.22	
-- Type        : Integer32
-- 
		iMAPNorthboundAlarmParas6 OBJECT-TYPE
			SYNTAX INTEGER
			ACCESS read-only
			STATUS mandatory
			DESCRIPTION
				"Reserved field 6"
			::= { iMAPNorthboundFaultAlarmNotification 22 }

		
--   Name        : iMAPNorthboundAlarmParas7
-- Description : Reserved field 7.
-- OID         : 1.3.6.1.4.1.2011.2.15.2.4.3.3.23	
-- Type        : Integer32
-- 
		iMAPNorthboundAlarmParas7 OBJECT-TYPE
			SYNTAX INTEGER
			ACCESS read-only
			STATUS mandatory
			DESCRIPTION
				"Reserved field 7"
			::= { iMAPNorthboundFaultAlarmNotification 23 }

		
--   Name        : iMAPNorthboundAlarmParas8
-- Description : Reserved field 8.
-- OID         : 1.3.6.1.4.1.2011.2.15.2.4.3.3.24	
-- Type        : Integer32
-- 
		iMAPNorthboundAlarmParas8 OBJECT-TYPE
			SYNTAX INTEGER
			ACCESS read-only
			STATUS mandatory
			DESCRIPTION
				"Reserved field 8"
			::= { iMAPNorthboundFaultAlarmNotification 24 }

		
--   Name        : iMAPNorthboundAlarmParas9
-- Description : Reserved field 9.
-- OID         : 1.3.6.1.4.1.2011.2.15.2.4.3.3.25	
-- Type        : Integer32
-- 
		iMAPNorthboundAlarmParas9 OBJECT-TYPE
			SYNTAX INTEGER
			ACCESS read-only
			STATUS mandatory
			DESCRIPTION
				"Reserved field 9"
			::= { iMAPNorthboundFaultAlarmNotification 25 }

		
--   Name        : iMAPNorthboundAlarmParas10
-- Description : Original alarm level, 
--               defined by the device when the alarm is generated.
--               1 Critical 
--               2 Major
--               3 Minor
--               4 Warning
-- 
-- OID         : 1.3.6.1.4.1.2011.2.15.2.4.3.3.26	
-- Type        : Integer32
-- 
		iMAPNorthboundAlarmParas10 OBJECT-TYPE
			SYNTAX INTEGER
			ACCESS read-only
			STATUS mandatory
			DESCRIPTION
				"Reserved field 10"
			::= { iMAPNorthboundFaultAlarmNotification 26 }

		
--   Name        : iMAPNorthboundAlarmExtendInfo
-- Description : Alarm extended information, including the 
--               location information of the alarm.
-- 
-- OID         : 1.3.6.1.4.1.2011.2.15.2.4.3.3.27	
-- Type        : Octet String
-- 
		iMAPNorthboundAlarmExtendInfo OBJECT-TYPE
			SYNTAX OCTET STRING
			ACCESS read-only
			STATUS mandatory
			DESCRIPTION
				"Extended information (max: 250 characters)
				Alarm extended information, including the location information of the alarm."
			::= { iMAPNorthboundFaultAlarmNotification 27 }

		
--   Name        : iMAPNorthboundAlarmProbablecause
-- Description : Probable cause of the alarm.
-- 
-- OID         : 1.3.6.1.4.1.2011.2.15.2.4.3.3.28	
-- Type        : Octet String
-- 
		iMAPNorthboundAlarmProbablecause OBJECT-TYPE
			SYNTAX OCTET STRING
			ACCESS read-only
			STATUS mandatory
			DESCRIPTION
				"Probable cause of the alarm"
			::= { iMAPNorthboundFaultAlarmNotification 28 }

		
--   Name        : iMAPNorthboundAlarmProposedrepairactions
-- Description : Alarm repair recommendations.
-- 
-- OID         : 1.3.6.1.4.1.2011.2.15.2.4.3.3.29	
-- Type        : Octet String
-- 
		iMAPNorthboundAlarmProposedrepairactions OBJECT-TYPE
			SYNTAX OCTET STRING
			ACCESS read-only
			STATUS mandatory
			DESCRIPTION
				"Alarm repair recommendations"
			::= { iMAPNorthboundFaultAlarmNotification 29 }

		
--   Name        : iMAPNorthboundAlarmSpecificproblems
-- Description : Alarm detailed reasons.
-- 
-- OID         : 1.3.6.1.4.1.2011.2.15.2.4.3.3.30	
-- Type        : Octet String
-- 
		iMAPNorthboundAlarmSpecificproblems OBJECT-TYPE
			SYNTAX OCTET STRING
			ACCESS read-only
			STATUS mandatory
			DESCRIPTION
				"Alarm detailed reasons"
			::= { iMAPNorthboundFaultAlarmNotification 30 }

		
--   Name        : iMAPNorthboundAlarmExtendProductItem1
-- Description : Extended product information as per Huawei Alarm Specification.
-- 
-- OID         : 1.3.6.1.4.1.2011.2.15.2.4.3.3.31	
-- Type        : Octet String
-- 
		iMAPNorthboundAlarmExtendProductItem1 OBJECT-TYPE
			SYNTAX OCTET STRING
			ACCESS read-only
			STATUS mandatory
			DESCRIPTION
				"This is one of 15 extensible alarm fields to be
				reported as part of alarm information. The fields
				to be reported are decided by the configuration
				for the SNMP agent in file snmpsvc.xml. For
				string type parameters the maximum supported
				length is 250 characters. If string is longer it
				will be truncated to 250 characters."
			::= { iMAPNorthboundFaultAlarmNotification 31 }

		
--   Name        : iMAPNorthboundAlarmExtendProductItem2
-- Description : Extended product information as per Huawei Alarm Specification.
-- 
-- OID         : 1.3.6.1.4.1.2011.2.15.2.4.3.3.32	
-- Type        : Octet String
-- 
		iMAPNorthboundAlarmExtendProductItem2 OBJECT-TYPE
			SYNTAX OCTET STRING
			ACCESS read-only
			STATUS mandatory
			DESCRIPTION
				"This is one of 15 extensible alarm fields to be
				reported as part of alarm information. The fields
				to be reported are decided by the configuration
				for the SNMP agent in file snmpsvc.xml. For
				string type parameters the maximum supported
				length is 250 characters. If string is longer it
				will be truncated to 250 characters."
			::= { iMAPNorthboundFaultAlarmNotification 32 }

		
--   Name        : iMAPNorthboundAlarmExtendProductItem3
-- Description : Extended product information as per Huawei Alarm Specification.
-- 
-- OID         : 1.3.6.1.4.1.2011.2.15.2.4.3.3.33	
-- Type        : Octet String
-- 
		iMAPNorthboundAlarmExtendProductItem3 OBJECT-TYPE
			SYNTAX OCTET STRING
			ACCESS read-only
			STATUS mandatory
			DESCRIPTION
				"This is one of 15 extensible alarm fields to be
				reported as part of alarm information. The fields
				to be reported are decided by the configuration
				for the SNMP agent in file snmpsvc.xml. For
				string type parameters the maximum supported
				length is 250 characters. If string is longer it
				will be truncated to 250 characters."
			::= { iMAPNorthboundFaultAlarmNotification 33 }

		
--   Name        : iMAPNorthboundAlarmExtendProductItem4
-- Description : Extended product information as per Huawei Alarm Specification.
-- 
-- OID         : 1.3.6.1.4.1.2011.2.15.2.4.3.3.34	
-- Type        : Octet String
-- 
		iMAPNorthboundAlarmExtendProductItem4 OBJECT-TYPE
			SYNTAX OCTET STRING
			ACCESS read-only
			STATUS mandatory
			DESCRIPTION
				"This is one of 15 extensible alarm fields to be
				reported as part of alarm information. The fields
				to be reported are decided by the configuration
				for the SNMP agent in file snmpsvc.xml. For
				string type parameters the maximum supported
				length is 250 characters. If string is longer it
				will be truncated to 250 characters."
			::= { iMAPNorthboundFaultAlarmNotification 34 }

		
--   Name        : iMAPNorthboundAlarmExtendProductItem5
-- Description : Extended product information as per Huawei Alarm Specification.
-- 
-- OID         : 1.3.6.1.4.1.2011.2.15.2.4.3.3.35	
-- Type        : Octet String
-- 
		iMAPNorthboundAlarmExtendProductItem5 OBJECT-TYPE
			SYNTAX OCTET STRING
			ACCESS read-only
			STATUS mandatory
			DESCRIPTION
				"This is one of 15 extensible alarm fields to be
				reported as part of alarm information. The fields
				to be reported are decided by the configuration
				for the SNMP agent in file snmpsvc.xml. For
				string type parameters the maximum supported
				length is 250 characters. If string is longer it
				will be truncated to 250 characters."
			::= { iMAPNorthboundFaultAlarmNotification 35 }

		
--   Name        : iMAPNorthboundAlarmExtendProductItem6
-- Description : Extended product information as per Huawei Alarm Specification.
-- 
-- OID         : 1.3.6.1.4.1.2011.2.15.2.4.3.3.36	
-- Type        : Octet String
-- 
		iMAPNorthboundAlarmExtendProductItem6 OBJECT-TYPE
			SYNTAX OCTET STRING
			ACCESS read-only
			STATUS mandatory
			DESCRIPTION
				"This is one of 15 extensible alarm fields to be
				reported as part of alarm information. The fields
				to be reported are decided by the configuration
				for the SNMP agent in file snmpsvc.xml. For
				string type parameters the maximum supported
				length is 250 characters. If string is longer it
				will be truncated to 250 characters."
			::= { iMAPNorthboundFaultAlarmNotification 36 }

		
--   Name        : iMAPNorthboundAlarmExtendProductItem7
-- Description : Extended product information as per Huawei Alarm Specification.
-- 
-- OID         : 1.3.6.1.4.1.2011.2.15.2.4.3.3.37	
-- Type        : Octet String
-- 
		iMAPNorthboundAlarmExtendProductItem7 OBJECT-TYPE
			SYNTAX OCTET STRING
			ACCESS read-only
			STATUS mandatory
			DESCRIPTION
				"This is one of 15 extensible alarm fields to be
				reported as part of alarm information. The fields
				to be reported are decided by the configuration
				for the SNMP agent in file snmpsvc.xml. For
				string type parameters the maximum supported
				length is 250 characters. If string is longer it
				will be truncated to 250 characters."
			::= { iMAPNorthboundFaultAlarmNotification 37 }

		
--   Name        : iMAPNorthboundAlarmExtendProductItem8
-- Description : Extended product information as per Huawei Alarm Specification.
-- 
-- OID         : 1.3.6.1.4.1.2011.2.15.2.4.3.3.38	
-- Type        : Octet String
-- 
		iMAPNorthboundAlarmExtendProductItem8 OBJECT-TYPE
			SYNTAX OCTET STRING
			ACCESS read-only
			STATUS mandatory
			DESCRIPTION
				"This is one of 15 extensible alarm fields to be
				reported as part of alarm information. The fields
				to be reported are decided by the configuration
				for the SNMP agent in file snmpsvc.xml. For
				string type parameters the maximum supported
				length is 250 characters. If string is longer it
				will be truncated to 250 characters."
			::= { iMAPNorthboundFaultAlarmNotification 38 }

		
--   Name        : iMAPNorthboundAlarmExtendProductItem9
-- Description : Extended product information as per Huawei Alarm Specification.
-- 
-- OID         : 1.3.6.1.4.1.2011.2.15.2.4.3.3.39	
-- Type        : Octet String
-- 
		iMAPNorthboundAlarmExtendProductItem9 OBJECT-TYPE
			SYNTAX OCTET STRING
			ACCESS read-only
			STATUS mandatory
			DESCRIPTION
				"This is one of 15 extensible alarm fields to be
				reported as part of alarm information. The fields
				to be reported are decided by the configuration
				for the SNMP agent in file snmpsvc.xml. For
				string type parameters the maximum supported
				length is 250 characters. If string is longer it
				will be truncated to 250 characters."
			::= { iMAPNorthboundFaultAlarmNotification 39 }

		
--   Name        : iMAPNorthboundAlarmExtendProductItem10
-- Description : Extended product information as per Huawei Alarm Specification.
-- 
-- OID         : 1.3.6.1.4.1.2011.2.15.2.4.3.3.40	
-- Type        : Octet String
-- 
		iMAPNorthboundAlarmExtendProductItem10 OBJECT-TYPE
			SYNTAX OCTET STRING
			ACCESS read-only
			STATUS mandatory
			DESCRIPTION
				"This is one of 15 extensible alarm fields to be
				reported as part of alarm information. The fields
				to be reported are decided by the configuration
				for the SNMP agent in file snmpsvc.xml. For
				string type parameters the maximum supported
				length is 250 characters. If string is longer it
				will be truncated to 250 characters."
			::= { iMAPNorthboundFaultAlarmNotification 40 }

		
--   Name        : iMAPNorthboundAlarmExtendProductItem11
-- Description : Extended product information as per Huawei Alarm Specification.
-- 
-- OID         : 1.3.6.1.4.1.2011.2.15.2.4.3.3.41	
-- Type        : Octet String
-- 
		iMAPNorthboundAlarmExtendProductItem11 OBJECT-TYPE
			SYNTAX OCTET STRING
			ACCESS read-only
			STATUS mandatory
			DESCRIPTION
				"This is one of 15 extensible alarm fields to be
				reported as part of alarm information. The fields
				to be reported are decided by the configuration
				for the SNMP agent in file snmpsvc.xml. For
				string type parameters the maximum supported
				length is 250 characters. If string is longer it
				will be truncated to 250 characters."
			::= { iMAPNorthboundFaultAlarmNotification 41 }

		
--   Name        : iMAPNorthboundAlarmExtendProductItem12
-- Description : Extended product information as per Huawei Alarm Specification.
-- 
-- OID         : 1.3.6.1.4.1.2011.2.15.2.4.3.3.42
-- Type        : Octet String
-- 
		iMAPNorthboundAlarmExtendProductItem12 OBJECT-TYPE
			SYNTAX OCTET STRING
			ACCESS read-only
			STATUS mandatory
			DESCRIPTION
				"This is one of 15 extensible alarm fields to be
				reported as part of alarm information. The fields
				to be reported are decided by the configuration
				for the SNMP agent in file snmpsvc.xml. For
				string type parameters the maximum supported
				length is 250 characters. If string is longer it
				will be truncated to 250 characters."
			::= { iMAPNorthboundFaultAlarmNotification 42 }

		
--   Name        : iMAPNorthboundAlarmExtendProductItem13
-- Description : Extended product information as per Huawei Alarm Specification.
-- 
-- OID         : 1.3.6.1.4.1.2011.2.15.2.4.3.3.43	
-- Type        : Octet String
-- 
		iMAPNorthboundAlarmExtendProductItem13 OBJECT-TYPE
			SYNTAX OCTET STRING
			ACCESS read-only
			STATUS mandatory
			DESCRIPTION
				"This is one of 15 extensible alarm fields to be
				reported as part of alarm information. The fields
				to be reported are decided by the configuration
				for the SNMP agent in file snmpsvc.xml. For
				string type parameters the maximum supported
				length is 250 characters. If string is longer it
				will be truncated to 250 characters."
			::= { iMAPNorthboundFaultAlarmNotification 43 }

		
--   Name        : iMAPNorthboundAlarmExtendProductItem14
-- Description : Extended product information as per Huawei Alarm Specification.
-- 
-- OID         : 1.3.6.1.4.1.2011.2.15.2.4.3.3.44	
-- Type        : Octet String
-- 
		iMAPNorthboundAlarmExtendProductItem14 OBJECT-TYPE
			SYNTAX OCTET STRING
			ACCESS read-only
			STATUS mandatory
			DESCRIPTION
				"This is one of 15 extensible alarm fields to be
				reported as part of alarm information. The fields
				to be reported are decided by the configuration
				for the SNMP agent in file snmpsvc.xml. For
				string type parameters the maximum supported
				length is 250 characters. If string is longer it
				will be truncated to 250 characters."
			::= { iMAPNorthboundFaultAlarmNotification 44 }

		
--   Name        : iMAPNorthboundAlarmExtendProductItem15
-- Description : Extended product information as per Huawei Alarm Specification.
-- 
-- OID         : 1.3.6.1.4.1.2011.2.15.2.4.3.3.45	
-- Type        : Octet String
-- 
		iMAPNorthboundAlarmExtendProductItem15 OBJECT-TYPE
			SYNTAX OCTET STRING
			ACCESS read-only
			STATUS mandatory
			DESCRIPTION
				"This is one of 15 extensible alarm fields to be
				reported as part of alarm information. The fields
				to be reported are decided by the configuration
				for the SNMP agent in file snmpsvc.xml. For
				string type parameters the maximum supported
				length is 250 characters. If string is longer it
				will be truncated to 250 characters."
			::= { iMAPNorthboundFaultAlarmNotification 45 }

		
--   Name        : iMAPNorthboundAlarmClearOperator
-- Description : The operator who cleared this alarm.
-- OID         : 1.3.6.1.4.1.2011.2.15.2.4.3.3.46	
-- Type        : Octet String
-- 
		iMAPNorthboundAlarmClearOperator OBJECT-TYPE
			SYNTAX OCTET STRING (SIZE (0..255))
			ACCESS read-only
			STATUS mandatory
			DESCRIPTION
				"The operator who cleared this alarm."
			::= { iMAPNorthboundFaultAlarmNotification 46 }

		
--   Name        : iMAPNorthboundAlarmObjectInstanceType
-- Description : Object instance type for the raised alarm.
-- OID         : 1.3.6.1.4.1.2011.2.15.2.4.3.3.47	
-- Type        : Octet String
-- 
		iMAPNorthboundAlarmObjectInstanceType OBJECT-TYPE
			SYNTAX OCTET STRING
			ACCESS read-only
			STATUS mandatory
			DESCRIPTION
				"Object instance type for the raised alarm"
			::= { iMAPNorthboundFaultAlarmNotification 47 }

		
--   Name        : iMAPNorthboundAlarmClearCategory
-- Description : Clear Category of Alarms.
-- OID         : 1.3.6.1.4.1.2011.2.15.2.4.3.3.48	
-- Type        : Octet String
-- 
		iMAPNorthboundAlarmClearCategory OBJECT-TYPE
			SYNTAX OCTET STRING
			ACCESS read-only
			STATUS mandatory
			DESCRIPTION
				"This specifies the Clear Category of alarms.
				0 
				1 - ADAC (Automatically Detected Automcatically Cleared)
				2 - ADMC (Automatically Detected Manually Cleared)"
			::= { iMAPNorthboundFaultAlarmNotification 48 }

		
--   Name        : iMAPNorthboundAlarmClearType
-- Description : Clear type of alarms.
-- OID         : 1.3.6.1.4.1.2011.2.15.2.4.3.3.49	
-- Type        : Octet String
-- 
		iMAPNorthboundAlarmClearType OBJECT-TYPE
			SYNTAX OCTET STRING
			ACCESS read-only
			STATUS mandatory
			DESCRIPTION
				"This specifies the Clear Type of alarms.
				0
				1 - Normal Clear
				2 - Restore Clear
				3 - Manual Clear
				4 - Configure Clear
				5 - Co-relation Clear"
			::= { iMAPNorthboundFaultAlarmNotification 49 }

		
--   Name        : iMAPNorthboundAlarmServiceAffectFlag
-- Description : Affecting service flag
-- OID         : 1.3.6.1.4.1.2011.2.15.2.4.3.3.50	
-- Type        : Octet String
-- 
		iMAPNorthboundAlarmServiceAffectFlag OBJECT-TYPE
			SYNTAX OCTET STRING
			ACCESS read-only
			STATUS mandatory
			DESCRIPTION
				"Affecting service flag for the alarm"
			::= { iMAPNorthboundFaultAlarmNotification 50 }

		
--   Name        : iMAPNorthboundAlarmAdditionalInfo
-- Description : Additional Information.
-- OID         : 1.3.6.1.4.1.2011.2.15.2.4.3.3.51	
-- Type        : Octet String
-- 
		iMAPNorthboundAlarmAdditionalInfo OBJECT-TYPE
			SYNTAX OCTET STRING (SIZE (0..250))
			ACCESS read-only
			STATUS mandatory
			DESCRIPTION
				"Additional Information regarding the alarm"
			::= { iMAPNorthboundFaultAlarmNotification 51 }

		
		iMAPNorthboundFaultAcknowledge OBJECT IDENTIFIER ::= { iMAPNorthboundFault 4 }

		
--    iMAPNorthboundAlarmAcknowledge - Leaf node that acknowledges
-- fault alarms. If the MIB node is set with valid alarm serial
-- numbers, then iMAP acknowledges fault alarms and notifies
-- to the NMS.
-- 
-- OID = 1.3.6.1.4.1.2011.2.15.2.4.4.1
-- 
		iMAPNorthboundAlarmAcknowledge OBJECT-TYPE
			SYNTAX OCTET STRING
			ACCESS read-write
			STATUS mandatory
			DESCRIPTION
				" Give serial number(s) of alarms to be acknowledged.
				Multiple serial numbers are separated by comma(,).
				Alarms serial number(s) are of type unsigned long and
				incompatible types are automatically considered
				as invalid serial number(s). Get attempt on this node
				will result in error.
				
				Output: Serial number(s) of alarms which could not be
				acknowledged. This also contains Alarm serial number(s)
				with incorrect syntax. If all alarms are successfully
				acknowledged then output is blank."
			::= { iMAPNorthboundFaultAcknowledge 1 }

		
		iMAPNorthboundFaultUnAcknowledge OBJECT IDENTIFIER ::= { iMAPNorthboundFault 5 }

		
--   iMAPNorthboundAlarmUnAcknowledge - Leaf node that unacknowledges
-- fault alarms. If the MIB node is set with valid alarm serial
-- numbers, then iMAP unacknowledges fault alarms and notifies
-- to the NMS. 
-- 
-- OID = 1.3.6.1.4.1.2011.2.15.2.4.5.1
-- 
		iMAPNorthboundAlarmUnAcknowledge OBJECT-TYPE
			SYNTAX OCTET STRING
			ACCESS read-write
			STATUS mandatory
			DESCRIPTION
				" Give serial number(s) of alarms to be unacknowledged.
				Multiple serial numbers are separated by comma(,).
				Alarms serial number(s) are of type unsigned long and
				incompatible types are automatically considered
				as invalid serial number(s). Get attempt on this node
				will result in error.
				
				Output: Serial number(s) of alarms which could not be
				unacknowledged. This also contains Alarm serial number(s)
				with incorrect syntax. If all alarms are successfully
				unacknowledged then output is blank."
			::= { iMAPNorthboundFaultUnAcknowledge 1 }

		
		iMAPNorthboundFaultClear OBJECT IDENTIFIER ::= { iMAPNorthboundFault 6 }

		
--   iMAPNorthboundAlarmClear - Leaf node that clears fault alarms.
-- If the MIB node is set with valid alarm serial numbers, then
-- iMAP clears fault alarms and notifies to the NMS.
-- 
-- OID = 1.3.6.1.4.1.2011.2.15.2.4.6.1
-- 
		iMAPNorthboundAlarmClear OBJECT-TYPE
			SYNTAX OCTET STRING
			ACCESS read-write
			STATUS mandatory
			DESCRIPTION
				" Give serial number(s) of alarms to be cleared.
				Multiple serial numbers are separated by comma(,).
				Alarms serial number(s)are of type unsigned long and
				incompatible types are automatically considered
				as invalid serial number(s). Get attempt on this node
				will result in error.
				
				Output: Serial number(s) of alarms which could not be
				cleared. This also contains Alarm serial number(s)
				with incorrect syntax. If all alarms are successfully
				cleared then output is blank."
			::= { iMAPNorthboundFaultClear 1 }

		
		iMAPConformance OBJECT IDENTIFIER ::= { iMAP 3 }

		
		iMAPGroups OBJECT IDENTIFIER ::= { iMAPConformance 1 }

		
--   The OBJECT-GROUP for SNMP Northbound Interface
-- 
		currentObjectGroup OBJECT IDENTIFIER ::= { iMAPGroups 1 }

		
--   The NOTIFICATION-GROUP for SNMP Northbound Interface.
-- Consists of:
--              1. Alarm Report Notification
--              2. Alarm Query Begin Notification
--              3. Alarm Query Notification
--              4. Alarm Query End Notification
--              5. HeartBeat Notification
-- 
		currentNotificationGroup OBJECT IDENTIFIER ::= { iMAPGroups 2 }

		
		iMAPCompliances OBJECT IDENTIFIER ::= { iMAPConformance 2 }

		
--   MODULE-COMPLIANCE for SNMP Northbound Interface
-- 
		basicCompliance OBJECT IDENTIFIER ::= { iMAPCompliances 1 }

		
-- The iMAP system sends real-time alarms to the NMS using this trap.
-- If an alarm occurs to an NE or the iMAP, the iMAP sends the alarm
-- trap to the NMS.
-- 
-- OID = 1.3.6.1.4.1.2011.2.15.2.4.3.3.0.1
-- 
		iMAPNorthboundFaultAlarmReportNotificationType TRAP-TYPE 
			ENTERPRISE iMAPNorthboundFaultAlarmNotification
			VARIABLES { iMAPNorthboundAlarmCSN, iMAPNorthboundAlarmCategory, iMAPNorthboundAlarmOccurTime, iMAPNorthboundAlarmMOName, iMAPNorthboundAlarmProductID, 
				iMAPNorthboundAlarmNEType, iMAPNorthboundAlarmNEDevID, iMAPNorthboundAlarmDevCsn, iMAPNorthboundAlarmID, iMAPNorthboundAlarmType, 
				iMAPNorthboundAlarmLevel, iMAPNorthboundAlarmRestore, iMAPNorthboundAlarmConfirm, iMAPNorthboundAlarmAckTime, iMAPNorthboundAlarmRestoreTime, 
				iMAPNorthboundAlarmOperator, iMAPNorthboundAlarmParas1, iMAPNorthboundAlarmParas2, iMAPNorthboundAlarmParas3, iMAPNorthboundAlarmParas4, 
				iMAPNorthboundAlarmParas5, iMAPNorthboundAlarmParas6, iMAPNorthboundAlarmParas7, iMAPNorthboundAlarmParas8, iMAPNorthboundAlarmParas9, 
				iMAPNorthboundAlarmParas10, iMAPNorthboundAlarmExtendInfo, iMAPNorthboundAlarmProbablecause, iMAPNorthboundAlarmProposedrepairactions, iMAPNorthboundAlarmSpecificproblems, 
				iMAPNorthboundAlarmExtendProductItem1, iMAPNorthboundAlarmExtendProductItem2, iMAPNorthboundAlarmExtendProductItem3, iMAPNorthboundAlarmExtendProductItem4, iMAPNorthboundAlarmExtendProductItem5, 
				iMAPNorthboundAlarmExtendProductItem6, iMAPNorthboundAlarmExtendProductItem7, iMAPNorthboundAlarmExtendProductItem8, iMAPNorthboundAlarmExtendProductItem9, iMAPNorthboundAlarmExtendProductItem10, 
				iMAPNorthboundAlarmExtendProductItem11, iMAPNorthboundAlarmExtendProductItem12, iMAPNorthboundAlarmExtendProductItem13, iMAPNorthboundAlarmExtendProductItem14, iMAPNorthboundAlarmExtendProductItem15, 
				iMAPNorthboundAlarmClearOperator, iMAPNorthboundAlarmAdditionalInfo, iMAPNorthboundAlarmClearType, iMAPNorthboundAlarmClearCategory, iMAPNorthboundAlarmServiceAffectFlag, 
				iMAPNorthboundAlarmObjectInstanceType }
			DESCRIPTION 
				"The iMAP system sends real-time alarms to the NMS using this trap.
				If an alarm occurs to an NE or the iMAP, the iMAP sends the alarm
				trap to the NMS."
			::=  1

--     The iMAP notifies the NMS of the start of the query.
-- After the NMS receives the active/current alarm query start 
-- trap, the query starts.
-- 
-- The trap is triggered by NMS for alarm query.
-- OID = 1.3.6.1.4.1.2011.2.15.2.4.3.3.0.2
		iMAPNorthboundFaultAlarmQueryBeginNotificationType TRAP-TYPE 
			ENTERPRISE iMAPNorthboundFaultAlarmNotification
			DESCRIPTION 
				"The iMAP notifies the NMS of the start of the query.
				After the NMS receives the active/current alarm query start 
				trap, the query starts.
				
				The trap is triggered by NMS for alarm query."
			::=  2

--   The iMAP system sends queried alarms to the NMS using this trap.
-- 
-- OID =  1.3.6.1.4.1.2011.2.15.2.4.3.3.0.3
		iMAPNorthboundFaultAlarmQueryNotificationType TRAP-TYPE 
			ENTERPRISE iMAPNorthboundFaultAlarmNotification
			VARIABLES { iMAPNorthboundAlarmCSN, iMAPNorthboundAlarmCategory, iMAPNorthboundAlarmOccurTime, iMAPNorthboundAlarmMOName, iMAPNorthboundAlarmProductID, 
				iMAPNorthboundAlarmNEType, iMAPNorthboundAlarmNEDevID, iMAPNorthboundAlarmDevCsn, iMAPNorthboundAlarmID, iMAPNorthboundAlarmType, 
				iMAPNorthboundAlarmLevel, iMAPNorthboundAlarmRestore, iMAPNorthboundAlarmConfirm, iMAPNorthboundAlarmAckTime, iMAPNorthboundAlarmRestoreTime, 
				iMAPNorthboundAlarmOperator, iMAPNorthboundAlarmParas1, iMAPNorthboundAlarmParas2, iMAPNorthboundAlarmParas3, iMAPNorthboundAlarmParas4, 
				iMAPNorthboundAlarmParas5, iMAPNorthboundAlarmParas6, iMAPNorthboundAlarmParas7, iMAPNorthboundAlarmParas8, iMAPNorthboundAlarmParas9, 
				iMAPNorthboundAlarmParas10, iMAPNorthboundAlarmExtendInfo, iMAPNorthboundAlarmProbablecause, iMAPNorthboundAlarmProposedrepairactions, iMAPNorthboundAlarmSpecificproblems, 
				iMAPNorthboundAlarmExtendProductItem1, iMAPNorthboundAlarmExtendProductItem2, iMAPNorthboundAlarmExtendProductItem3, iMAPNorthboundAlarmExtendProductItem4, iMAPNorthboundAlarmExtendProductItem5, 
				iMAPNorthboundAlarmExtendProductItem6, iMAPNorthboundAlarmExtendProductItem7, iMAPNorthboundAlarmExtendProductItem8, iMAPNorthboundAlarmExtendProductItem9, iMAPNorthboundAlarmExtendProductItem10, 
				iMAPNorthboundAlarmExtendProductItem11, iMAPNorthboundAlarmExtendProductItem12, iMAPNorthboundAlarmExtendProductItem13, iMAPNorthboundAlarmExtendProductItem14, iMAPNorthboundAlarmExtendProductItem15, 
				iMAPNorthboundAlarmClearOperator, iMAPNorthboundAlarmAdditionalInfo, iMAPNorthboundAlarmServiceAffectFlag, iMAPNorthboundAlarmClearType, iMAPNorthboundAlarmClearCategory, 
				iMAPNorthboundAlarmObjectInstanceType }
			DESCRIPTION 
				" The iMAP system sends queried alarms to the NMS using this trap."
			::=  3

--   The iMAP notifies the NMS of the stop of the query.
-- After the NMS receives the active/current alarm query stop
-- trap, it indicates that the query ends.
-- 
-- The NMS triggers the stop of the query, or the query
-- ends after the NMS receives the active/current alarms.
-- 
-- OID = 1.3.6.1.4.1.2011.2.15.2.4.3.3.0.4
-- 
		iMAPNorthboundFaultAlarmQueryEndNotificationType TRAP-TYPE 
			ENTERPRISE iMAPNorthboundFaultAlarmNotification
			DESCRIPTION 
				" The iMAP notifies the NMS of the stop of the query.
				After the NMS receives the active/current alarm query stop
				trap, it indicates that the query ends.
				
				The NMS triggers the stop of the query, or the query
				ends after the NMS receives the active/current alarms."
			::=  4

--   The iMAP sends the heartbeat notification trap to the NMS
-- regularly each period. If the NMS receives the trap, the
-- connection between the NMS and the iMAP works. If not, 
-- the connection fails.
-- 
-- OID = 1.3.6.1.4.1.2011.2.15.2.1.2.1.1.1.0.5
		iMAPNorthboundHeartbeatNotificationType TRAP-TYPE 
			ENTERPRISE iMAPNorthboundHeartbeatNotification
			VARIABLES { iMAPNorthboundHeartbeatSystemLabel, iMAPNorthboundHeartbeatPeriod, iMAPNorthboundHeartbeatTimeStamp }
			DESCRIPTION 
				" The iMAP sends the heartbeat notification trap to the NMS
				regularly each period. If the NMS receives the trap, the
				connection between the NMS and the iMAP works. If not, 
				the connection fails."
			::=  5

	
	END

--
-- IMAP_NORTHBOUND_MIB-V1.mib
